Attribute VB_Name = "EngCad_Autocad_Draw"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Public Function Arc(space As AcActiveSpace, CenterX As Variant, CenterY As Variant, CenterZ As Variant, Radious As Variant, StartAngle As Variant, EndAngle As Variant, Optional Color As AcColor, Optional layer As String)
Dim ArcObj As AcadArc
Dim center(0 To 2) As Double
StartAngle = (StartAngle * 3.14159265358979) / 180
EndAngle = (EndAngle * 3.14159265358979) / 180
center(0) = CenterX: center(1) = CenterY: center(2) = CenterZ
If space = 0 Then Set ArcObj = AutoCAD.Application.ActiveDocument.PaperSpace.AddArc(center, Radious, StartAngle, EndAngle)
If space = 1 Then Set ArcObj = AutoCAD.Application.ActiveDocument.modelspace.AddArc(center, Radious, StartAngle, EndAngle)
On Error Resume Next
ArcObj.Color = Color
ArcObj.layer = layer
End Function

Public Function linea(space As AcActiveSpace, StartX As Variant, StartY As Variant, StartZ As Variant, EndX As Variant, EndY As Variant, EndZ As Variant, Optional Color As AcColor, Optional layer As String)
Dim LineObj As AcadLine: Dim StartPoint(0 To 2) As Double: Dim EndPoint(0 To 2) As Double
StartPoint(0) = StartX: StartPoint(1) = StartY: StartPoint(2) = StartZ
EndPoint(0) = EndX: EndPoint(1) = EndY: EndPoint(2) = EndZ
If space = 0 Then Set LineObj = AutoCAD.Application.ActiveDocument.PaperSpace.AddLine(StartPoint, EndPoint)
If space = 1 Then Set LineObj = AutoCAD.Application.ActiveDocument.modelspace.AddLine(StartPoint, EndPoint)
On Error Resume Next
LineObj.Color = Color
LineObj.layer = layer
End Function

Public Function Point(space As AcActiveSpace, CenterX As Variant, CenterY As Variant, CenterZ As Variant, Optional Color As AcColor, Optional layer As String)
Dim PointObj As AcadPoint
Dim Pnt(0 To 2) As Double
Pnt(0) = CenterX: Pnt(1) = CenterY: Pnt(2) = CenterZ
If space = 0 Then Set PointObj = AutoCAD.Application.ActiveDocument.PaperSpace.AddPoint(Pnt)
If space = 1 Then Set PointObj = AutoCAD.Application.ActiveDocument.modelspace.AddPoint(Pnt)
On Error Resume Next
PointObj.Color = Color
PointObj.layer = layer
End Function
Public Function ArcFromConsole(StartX As Variant, StartY As Variant, StartZ As Variant, EndX As Variant, EndY As Variant, EndZ As Variant, Radious As Variant)
StartX1 = acad.ChangebyDot(StartX): StartY1 = acad.ChangebyDot(StartY): StartZ1 = acad.ChangebyDot(StartZ)
EndX1 = acad.ChangebyDot(EndX): EndY1 = acad.ChangebyDot(EndY): EndZ1 = acad.ChangebyDot(EndZ)
firstpnt = StartX1 & "," & StartY1: endpnt = EndX1 & "," & EndY1: radi = acad.ChangebyDot(Radious)
AutoCAD.Application.ActiveDocument.SendCommand "arc" & vbCr & firstpnt & vbCr & "e" & vbCr & endpnt & vbCr & "r" & vbCr & radi & vbCr
End Function
Public Function Circulo(space As AcActiveSpace, CenterX As Variant, CenterY As Variant, CenterZ As Variant, Radious As Variant, Optional Color As AcColor, Optional layer As String)
Dim CirculoObj As AcadCircle
Dim Pnt(0 To 2) As Double
Pnt(0) = CenterX: Pnt(1) = CenterY: Pnt(2) = CenterZ
If space = 0 Then Set CirculoObj = AutoCAD.Application.ActiveDocument.PaperSpace.AddCircle(Pnt, Radious)
If space = 1 Then Set CirculoObj = AutoCAD.Application.ActiveDocument.modelspace.AddCircle(Pnt, Radious)
On Error Resume Next
CirculoObj.Color = Color
CirculoObj.layer = layer
End Function

Public Function XLine(space As AcActiveSpace, StartX As Variant, StartY As Variant, StartZ As Variant, EndX As Variant, EndY As Variant, EndZ As Double, Optional Color As AcColor, Optional layer As String)
Dim XLineObj As AcadXline: Dim StartPoint(0 To 2) As Double: Dim EndPoint(0 To 2) As Double
StartPoint(0) = StartX: StartPoint(1) = StartY: StartPoint(2) = StartZ
EndPoint(0) = EndX: EndPoint(1) = EndY: EndPoint(2) = EndZ
If space = 0 Then Set XLineObj = AutoCAD.Application.ActiveDocument.PaperSpace.AddXline(StartPoint, EndPoint)
If space = 1 Then Set XLineObj = AutoCAD.Application.ActiveDocument.modelspace.AddXline(StartPoint, EndPoint)
On Error Resume Next
XLineObj.Color = Color
XLineObj.layer = layer
End Function
Public Function MText(space As AcActiveSpace, StartX As Variant, StartY As Variant, StartZ As Variant, Width As Variant, CadenaTexto As Variant, Optional Color As AcColor, Optional layer As String)
Dim MTextObj As AcadMText: Dim PuntoA(0 To 2) As Double
PuntoA(0) = StartX: PuntoA(1) = StartY: PuntoA(2) = StartZ
If space = 0 Then Set MTextObj = AutoCAD.Application.ActiveDocument.PaperSpace.AddMText(PuntoA, Width, CadenaTexto)
If space = 1 Then Set MTextObj = AutoCAD.Application.ActiveDocument.modelspace.AddMText(PuntoA, Width, CadenaTexto)
On Error Resume Next
With MTextObj
.AttachmentPoint = acAttachmentPointMiddleLeft
.Color = Color
.insertionPoint = PuntoA
End With
On Error Resume Next
MTextObj.Color = Color
MTextObj.layer = layer
End Function
Public Function Rectangulo(space As AcActiveSpace, Ancho As Variant, Alto As Variant, BasePointX As Variant, BasePointY As Variant, Optional Color As AcColor, Optional layer As String)
linea space, BasePointX, BasePointY, 0, BasePointX + Ancho, BasePointY, 0
linea space, BasePointX, BasePointY + Alto, 0, BasePointX + Ancho, BasePointY + Alto, 0
linea space, BasePointX, BasePointY, 0, BasePointX, BasePointY + Alto, 0
linea space, BasePointX + Ancho, BasePointY, 0, BasePointX + Ancho, BasePointY + Alto, 0
AutoCAD.Application.ActiveDocument.SendCommand "regen" & vbCr
End Function
Public Function RectanguloPolyClosed(space As AcActiveSpace, Ancho As Variant, Alto As Variant, BasePointX As Variant, BasePointY As Variant, Optional Color As AcColor, Optional layer As String)
Dim Poly As AcadPolyline
Dim PuntoA(0 To 11) As Double
PuntoA(0) = BasePointX:             PuntoA(1) = BasePointY:             PuntoA(2) = 0
PuntoA(3) = BasePointX:             PuntoA(4) = BasePointY + Alto:      PuntoA(5) = 0
PuntoA(6) = BasePointX + Ancho:     PuntoA(7) = BasePointY + Alto:      PuntoA(8) = 0
PuntoA(9) = BasePointX + Ancho:     PuntoA(10) = BasePointY:      PuntoA(11) = 0
Set Poly = AutoCAD.Application.ActiveDocument.modelspace.AddPolyline(PuntoA)
Poly.Closed = True
On Error Resume Next
Poly.Color = Color
Poly.layer = layer
AutoCAD.Application.ActiveDocument.SendCommand "regen" & vbCr
End Function
Public Function Face3d(space As AcActiveSpace, Ancho As Variant, Alto As Variant, BasePointX As Variant, BasePointY As Variant, Optional Color As AcColor, Optional layer As String)
Dim Face3dObj As Acad3DFace: Dim PuntoA(0 To 2) As Double: Dim PuntoB(0 To 2) As Double: Dim PuntoC(0 To 2) As Double: Dim PuntoD(0 To 2) As Double
PuntoA(0) = BasePointX:             PuntoA(1) = BasePointY:             PuntoA(2) = 0
PuntoB(0) = BasePointX:             PuntoB(1) = BasePointY + Alto:      PuntoB(2) = 0
PuntoC(0) = BasePointX + Ancho:     PuntoC(1) = BasePointY + Alto:      PuntoC(2) = 0
PuntoD(0) = BasePointX + Ancho:     PuntoD(1) = BasePointY:             PuntoD(2) = 0
If space = 0 Then Set Face3dObj = AutoCAD.Application.ActiveDocument.PaperSpace.Add3DFace(PuntoA, PuntoB, PuntoC, PuntoD)
If space = 1 Then Set Face3dObj = AutoCAD.Application.ActiveDocument.modelspace.Add3DFace(PuntoA, PuntoB, PuntoC, PuntoD)
On Error Resume Next
Face3dObj.Color = Color
Face3dObj.layer = layer
AutoCAD.Application.ActiveDocument.SendCommand "regen" & vbCr
End Function

Public Function Cilindro3d(space As AcActiveSpace, CenterX As Variant, CenterY As Variant, CenterZ As Variant, Radious As Variant, Altura As Double, Direccion As Double, Optional Color As AcColor, Optional layer As String)
Dim Cilindro3dObj As Acad3DSolid: Dim Centro(0 To 2) As Double: Dim regionObj As Variant: Dim Circulo(0) As AcadCircle
Centro(0) = CenterX: Centro(1) = CenterY: Centro(2) = CenterZ
If space = 0 Then Set Circulo(0) = AutoCAD.Application.ActiveDocument.PaperSpace.AddCircle(Centro, Radious)
If space = 1 Then Set Circulo(0) = AutoCAD.Application.ActiveDocument.modelspace.AddCircle(Centro, Radious)
If space = 0 Then regionObj = AutoCAD.Application.ActiveDocument.PaperSpace.AddRegion(Circulo)
If space = 1 Then regionObj = AutoCAD.Application.ActiveDocument.modelspace.AddRegion(Circulo)
If space = 0 Then Set Cilindro3dObj = AutoCAD.Application.ActiveDocument.PaperSpace.AddExtrudedSolid(regionObj(0), Altura, Direccion)
If space = 1 Then Set Cilindro3dObj = AutoCAD.Application.ActiveDocument.modelspace.AddExtrudedSolid(regionObj(0), Altura, Direccion)
Circulo(0).Delete
regionObj(0).Delete
On Error Resume Next
Cilindro3dObj.Color = Color
Cilindro3dObj.layer = layer
AutoCAD.Application.ActiveDocument.SendCommand "regen" & vbCr
End Function

Attribute VB_Name = "EngCad_Autocad_Edition"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Dim entidad As AcadEntity
Dim Block As AcadBlockReference
Public Sub BuscayExplotaBloques()
Dim entidad As AcadEntity
For Each entidad In AutoCAD.Application.ActiveDocument.modelspace
If entidad.ObjectName = "AcDbDbBlockReference" Then
Set Block = entidad
Bloc.Explode
End If
Next entidad
End Sub
Public Function ReemplazaPolilineasYTrazaCentros(space As AcActiveSpace)
'esta macro reemplaza las polilineas por circulos, ademas traza lineas de eje
Dim entidad As AcadEntity
Dim Perimeter As Double
Dim Length As Variant
For Each entidad In AutoCAD.Application.ActiveDocument.modelspace
If entidad.ObjectName = "AcDbDbPolyline" Then
Length = Round(entidad.Length, 4)
End If
entidad.GetBoundingBox MinPoint, MaxPoint
radio = ((MaxPoint(0) - MinPoint(0)) / 2)
Pi = 3.14159265358979
PerimetroPosible = Round(radio * 2 * Pi, 4)
If PerimetroPosible = Length Then
d = radio
linea space, MinPoint(0) - d, MinPoint(1) + d, MinPoint(2), MaxPoint(0) + d, MaxPoint(1) - d, MaxPoint(2), acByLayer, "0"
linea space, MinPoint(0) + d, MinPoint(1) - d, MinPoint(2), MaxPoint(0) - d, MaxPoint(1) + d, MaxPoint(2), acByLayer, "0"
Circulo space, MinPoint(0) + d, MinPoint(1) + d, MinPoint(2), d, acByLayer, ".GENERAL ARRANGEMENT"
entidad.Delete
End If
Next entidad
ZoomExtents
End Function

Public Function BorrarEntidadesExepto(ent As AcEntityName)
Dim ObjVBA As String
If ent = 1 Then ObjVBA = "AcDb3dFace"
If ent = 2 Then ObjVBA = "AcDb3dPolyline"
If ent = 3 Then ObjVBA = "AcDb3dSolid"
If ent = 4 Then ObjVBA = "AcDbArc"
If ent = 5 Then ObjVBA = "AcDbAttribute"
If ent = 6 Then ObjVBA = "AcDbAttributeReference"
If ent = 7 Then ObjVBA = "AcDbBlockReference"
If ent = 8 Then ObjVBA = "AcDbCircle"
If ent = 47 Then ObjVBA = "AcDbDgnUnderlay"
If ent = 41 Then ObjVBA = "AcDbDim3PointAngular"
If ent = 9 Then ObjVBA = "AcDbDimAligned"
If ent = 10 Then ObjVBA = "AcDbDimAngular"
If ent = 44 Then ObjVBA = "AcDbDimArcLength"
If ent = 12 Then ObjVBA = "AcDbDimDiametric"
If ent = 13 Then ObjVBA = "AcDbDimOrdinate"
If ent = 14 Then ObjVBA = "AcDbDimRadial"
If ent = 45 Then ObjVBA = "AcDbDimRadialLarge"
If ent = 15 Then ObjVBA = "AcDbDimRotated"
If ent = 46 Then ObjVBA = "AcDbDwfUnderlay"
If ent = 16 Then ObjVBA = "AcDbEllipse"
If ent = 42 Then ObjVBA = "AcDbExternalReference"
If ent = 17 Then ObjVBA = "AcDbHatch"
If ent = 18 Then ObjVBA = "AcDbLeader"
If ent = 19 Then ObjVBA = "AcDbLine"
If ent = 38 Then ObjVBA = "AcDbMInsertBlock"
If ent = 48 Then ObjVBA = "AcDbMLeader"
If ent = 40 Then ObjVBA = "AcDbMLine"
If ent = 21 Then ObjVBA = "AcDbMtext"
If ent = 51 Then ObjVBA = "AcDbNurbSurface"
If ent = 50 Then ObjVBA = "AcDbPdfUnderlay"
If ent = 22 Then ObjVBA = "AcDbPoint"
If ent = 39 Then ObjVBA = "AcDbPolyfaceMesh"
If ent = 25 Then ObjVBA = "AcDbPolymesh"
If ent = 23 Then ObjVBA = "AcDbPolyline"
If ent = 35 Then ObjVBA = "AcDbPViewport"
If ent = 26 Then ObjVBA = "AcDbRaster"
If ent = 27 Then ObjVBA = "AcDbRay"
If ent = 28 Then ObjVBA = "AcDbRegion"
If ent = 29 Then ObjVBA = "AcDbShape"
If ent = 30 Then ObjVBA = "AcDbSolid"
If ent = 31 Then ObjVBA = "AcDbSpline"
If ent = 49 Then ObjVBA = "AcDbSubDMesh"
If ent = 43 Then ObjVBA = "AcDbTable"
If ent = 32 Then ObjVBA = "AcDbText"
If ent = 33 Then ObjVBA = "AcDbTolerance"
If ent = 34 Then ObjVBA = "AcDbTrace"
If ent = 36 Then ObjVBA = "AcDbXline"
Dim entidad As AcadEntity
For Each entidad In AutoCAD.Application.ActiveDocument.modelspace
If entidad.ObjectName = ObjVBA Then
Else
entidad.Delete
End If
Next entidad
AutoCAD.Application.ActiveDocument.SendCommand "regen" & vbCr
End Function

Public Function BorrarEntidades(ent As AcEntityName)
Dim ObjVBA As String
If ent = 1 Then ObjVBA = "AcDb3dFace"
If ent = 2 Then ObjVBA = "AcDb3dPolyline"
If ent = 3 Then ObjVBA = "AcDb3dSolid"
If ent = 4 Then ObjVBA = "AcDbArc"
If ent = 5 Then ObjVBA = "AcDbAttribute"
If ent = 6 Then ObjVBA = "AcDbAttributeReference"
If ent = 7 Then ObjVBA = "AcDbBlockReference"
If ent = 8 Then ObjVBA = "AcDbCircle"
If ent = 47 Then ObjVBA = "AcDbDgnUnderlay"
If ent = 41 Then ObjVBA = "AcDbDim3PointAngular"
If ent = 9 Then ObjVBA = "AcDbDimAligned"
If ent = 10 Then ObjVBA = "AcDbDimAngular"
If ent = 44 Then ObjVBA = "AcDbDimArcLength"
If ent = 12 Then ObjVBA = "AcDbDimDiametric"
If ent = 13 Then ObjVBA = "AcDbDimOrdinate"
If ent = 14 Then ObjVBA = "AcDbDimRadial"
If ent = 45 Then ObjVBA = "AcDbDimRadialLarge"
If ent = 15 Then ObjVBA = "AcDbDimRotated"
If ent = 46 Then ObjVBA = "AcDbDwfUnderlay"
If ent = 16 Then ObjVBA = "AcDbEllipse"
If ent = 42 Then ObjVBA = "AcDbExternalReference"
If ent = 17 Then ObjVBA = "AcDbHatch"
If ent = 18 Then ObjVBA = "AcDbLeader"
If ent = 19 Then ObjVBA = "AcDbLine"
If ent = 38 Then ObjVBA = "AcDbMInsertBlock"
If ent = 48 Then ObjVBA = "AcDbMLeader"
If ent = 40 Then ObjVBA = "AcDbMLine"
If ent = 21 Then ObjVBA = "AcDbMtext"
If ent = 51 Then ObjVBA = "AcDbNurbSurface"
If ent = 50 Then ObjVBA = "AcDbPdfUnderlay"
If ent = 22 Then ObjVBA = "AcDbPoint"
If ent = 39 Then ObjVBA = "AcDbPolyfaceMesh"
If ent = 25 Then ObjVBA = "AcDbPolymesh"
If ent = 23 Then ObjVBA = "AcDbPolyline"
If ent = 35 Then ObjVBA = "AcDbPViewport"
If ent = 26 Then ObjVBA = "AcDbRaster"
If ent = 27 Then ObjVBA = "AcDbRay"
If ent = 28 Then ObjVBA = "AcDbRegion"
If ent = 29 Then ObjVBA = "AcDbShape"
If ent = 30 Then ObjVBA = "AcDbSolid"
If ent = 31 Then ObjVBA = "AcDbSpline"
If ent = 49 Then ObjVBA = "AcDbSubDMesh"
If ent = 43 Then ObjVBA = "AcDbTable"
If ent = 32 Then ObjVBA = "AcDbText"
If ent = 33 Then ObjVBA = "AcDbTolerance"
If ent = 34 Then ObjVBA = "AcDbTrace"
If ent = 36 Then ObjVBA = "AcDbXline"
Dim entidad As AcadEntity
For Each entidad In AutoCAD.Application.ActiveDocument.modelspace
If entidad.ObjectName = ObjVBA Then
entidad.Delete
Else
End If
Next entidad
AutoCAD.Application.ActiveDocument.SendCommand "regen" & vbCr
End Function


Public Sub EliminarTodo()
e = AutoCAD.Application.ActiveDocument.modelspace.Count
If e > 0 Then
AutoCAD.Application.ActiveDocument.SendCommand "_ai_selall" & vbCr & "_.erase" & vbCr
Else:
End If
End Sub
Public Sub NuevoDibujo()
AutoCAD.Application.Documents.Add (acad)
End Sub
Public Function Seleccion(name As Variant, StartX As Variant, StartY As Variant, StartZ As Variant, EndX As Variant, EndY As Variant, EndZ As Variant)
Dim ssetObj As AcadSelectionSet
Dim mode As Integer: Dim PuntoA(0 To 2) As Double: Dim PuntoB(0 To 2) As Double
Set ssetObj = AutoCAD.Application.ActiveDocument.SelectionSets.Add(name)
mode = acSelectionSetCrossing
PuntoA(0) = StartX:     PuntoA(1) = StartY:         PuntoA(2) = StartZ
PuntoB(0) = EndX:       PuntoB(1) = EndY:           PuntoB(2) = EndZ
ssetObj.Select mode, PuntoA, PuntoB
End Function
Public Sub BorrarSelectionSets()
On Error Resume Next
Dim ssetObj As AcadSelectionSet
For Each ssetObj In AutoCAD.Application.ActiveDocument.SelectionSets
ssetObj.Delete
Next
End Sub
Public Function SelectAndDelete(StartX As Variant, StartY As Variant, EndX As Variant, EndY As Variant, Optional Modo As ModeSelect)
'acSelectionSetCrossing es lo que toca: 'acSelectionSetWindow    es lo que encierra
BorrarSelectionSets
Dim mode As Integer: Dim PuntoA(0 To 2) As Double: Dim PuntoB(0 To 2) As Double
Dim ssetObj As AcadSelectionSet
NameSelect = "SelectionTemporal"
PuntoA(0) = StartX: PuntoA(1) = StartY: PuntoA(2) = 0: PuntoB(0) = EndX: PuntoB(1) = EndY: PuntoB(2) = 0
Set ssetObj = AutoCAD.Application.ActiveDocument.SelectionSets.Add(NameSelect)
If Modo = 0 Then
mode = acSelectionSetWindow: ssetObj.Select mode, PuntoB, PuntoA
Else:
mode = acSelectionSetCrossing: ssetObj.Select mode, PuntoB, PuntoA
End If
ssetObj.Erase: ssetObj.Delete
End Function
Public Function CrearBloque(name As Variant, StartX As Variant, StartY As Variant, StartZ As Variant)
Dim blockObj As AcadBlock: Dim PuntoA(0 To 2) As Double
PuntoA(0) = StartX: PuntoA(1) = StartY: PuntoA(2) = StartZ
Set blockObj = AutoCAD.ActiveDocument.Blocks.Add(PuntoA, name)
End Function


Public Function InsertBlockName(space As AcActiveSpace, name As String, StartX As Variant, StartY As Variant, StartZ As Variant)
Dim blockRefObj As AcadBlockReference: Dim PuntoA(0 To 2) As Double
PuntoA(0) = StartX: PuntoA(1) = StartY: PuntoA(2) = StartZ
If space = 0 Then Set blockRefObj = AutoCAD.Application.ActiveDocument.PaperSpace.InsertBlock(PuntoA, name, 1#, 1#, 1#, 0)
If space = 1 Then Set blockRefObj = AutoCAD.Application.ActiveDocument.modelspace.InsertBlock(PuntoA, name, 1#, 1#, 1#, 0)
End Function
Public Function ChangebyDot(value As Variant) As Variant
ChangebyDot = Replace(value, ",", ".")
End Function

Attribute VB_Name = "EngCad_Autocad_General"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Public Enum EngCadEntityName
AcDb2dPolyline
AcDb3dFace
AcDb3dPolyline
AcDb3dSolid
AcDbArc
AcDbAttribute
AcDbAttributeReference
AcDbBlockReference
AcDbCircle
AcDbDgnUnderlay
AcDbDim3PointAngular
AcDbDimAligned
AcDbDimAngular
AcDbDimArcLength
AcDbDimDiametric
AcDbDimOrdinate
AcDbDimRadial
AcDbDimRadialLarge
AcDbDimRotated
AcDbDwfUnderlay
AcDbEllipse
AcDbExternalReference
AcDbHatch
AcDbLeader
AcDbLine
AcDbMInsertBlock
AcDbMLeader
AcDbMLine
AcDbMtext
AcDbNurbSurface
AcDbPdfUnderlay
AcDbPoint
AcDbPolyfaceMesh
AcDbPolymesh
AcDbPolyline
AcDbPViewport
AcDbRaster
AcDbRay
AcDbRegion
AcDbShape
AcDbSolid
AcDbSpline
AcDbSubDMesh
AcDbTable
AcDbText
AcDbTolerance
AcDbTrace
AcDbXline
End Enum

Public Enum Espacios
modelspace
PaperSpace
End Enum

Public Enum UCSTypes
Previous
view
World
End Enum

Public Enum Views
Top
Bottom
Left
Right
Front
Back
SW_Isometric
SE_Isometric
NE_Isometric
NW_Isometric
End Enum

Public Enum Sombras
wireframe2d
Wireframe
HIDDEN
Realistic
Conceptual
Shaded
shaded_with_Edges
shades_of_Gray
SKetchy
X_ray
End Enum

Public Enum LayersAllied
X3D_MODEL
DIMENSION
GENERAL_ARRANGEMENT
HIDDEN
OUTLINE_1
OUTLINE_3
TEXT
TITLE_BLOCK_ATTRIBUTES
TITLE_BLOCK_OUTLINE
TITLE_BLOCK_TEXT
TITLE_PAGE_OUTLINE
CERO
CENTER_LINE
End Enum

Public Enum ModeSelect
LoQueEncierra
LoqueToca
End Enum


Public Property Get EnumToStringEngCadEntityName(EngCadEntityName) As String
Dim v As Variant
v = Array("AcDb2dPolyline", "AcDb3dFace", "AcDb3dPolyline", "AcDb3dSolid", "AcDbArc", "AcDbAttribute", "AcDbAttributeReference", "AcDbBlockReference", "AcDbCircle", "AcDbDgnUnderlay", "AcDbDim3PointAngular", "AcDbDimAligned", "AcDbDimAngular", "AcDbDimArcLength", "AcDbDimDiametric", "AcDbDimOrdinate", "AcDbDimRadial", "AcDbDimRadialLarge", "AcDbDimRotated", "AcDbDwfUnderlay", "AcDbEllipse", "AcDbExternalReference", "AcDbHatch", "AcDbLeader", "AcDbLine", "AcDbMInsertBlock", "AcDbMLeader", "AcDbMLine", "AcDbMtext", "AcDbNurbSurface", "AcDbPdfUnderlay", "AcDbPoint", "AcDbPolyfaceMesh", "AcDbPolymesh", "AcDbPolyline", "AcDbPViewport", "AcDbRaster", "AcDbRay", "AcDbRegion", "AcDbShape", "AcDbSolid", "AcDbSpline", "AcDbSubDMesh", "AcDbTable", "AcDbText", "AcDbTolerance", "AcDbTrace", "AcDbXline")
EngCadEntityNametoString = VBA.CStr(v(EngCadEntityName))
VBA.c
End Property
Public Function GetVBAEntityName(ent As Variant)
If ent = 0 Then GetVBAEntityName = "AcDb2dPolyline"
If ent = 1 Then GetVBAEntityName = "AcDb3dFace"
If ent = 2 Then GetVBAEntityName = "AcDb3dPolyline"
If ent = 3 Then GetVBAEntityName = "AcDb3dSolid"
If ent = 4 Then GetVBAEntityName = "AcDbArc"
If ent = 5 Then GetVBAEntityName = "AcDbAttribute"
If ent = 6 Then GetVBAEntityName = "AcDbAttributeReference"
If ent = 7 Then GetVBAEntityName = "AcDbBlockReference"
If ent = 8 Then GetVBAEntityName = "AcDbCircle"
If ent = 9 Then GetVBAEntityName = "AcDbDgnUnderlay"
If ent = 10 Then GetVBAEntityName = "AcDbDim3PointAngular"
If ent = 11 Then GetVBAEntityName = "AcDbDimAligned"
If ent = 12 Then GetVBAEntityName = "AcDbDimAngular"
If ent = 13 Then GetVBAEntityName = "AcDbDimArcLength"
If ent = 14 Then GetVBAEntityName = "AcDbDimDiametric"
If ent = 15 Then GetVBAEntityName = "AcDbDimOrdinate"
If ent = 16 Then GetVBAEntityName = "AcDbDimRadial"
If ent = 17 Then GetVBAEntityName = "AcDbDimRadialLarge"
If ent = 18 Then GetVBAEntityName = "AcDbDimRotated"
If ent = 19 Then GetVBAEntityName = "AcDbDwfUnderlay"
If ent = 20 Then GetVBAEntityName = "AcDbEllipse"
If ent = 21 Then GetVBAEntityName = "AcDbExternalReference"
If ent = 22 Then GetVBAEntityName = "AcDbHatch"
If ent = 23 Then GetVBAEntityName = "AcDbLeader"
If ent = 24 Then GetVBAEntityName = "AcDbLine"
If ent = 25 Then GetVBAEntityName = "AcDbMInsertBlock"
If ent = 26 Then GetVBAEntityName = "AcDbMLeader"
If ent = 27 Then GetVBAEntityName = "AcDbMLine"
If ent = 28 Then GetVBAEntityName = "AcDbMtext"
If ent = 29 Then GetVBAEntityName = "AcDbNurbSurface"
If ent = 30 Then GetVBAEntityName = "AcDbPdfUnderlay"
If ent = 31 Then GetVBAEntityName = "AcDbPoint"
If ent = 32 Then GetVBAEntityName = "AcDbPolyfaceMesh"
If ent = 33 Then GetVBAEntityName = "AcDbPolymesh"
If ent = 34 Then GetVBAEntityName = "AcDbPolyline"
If ent = 35 Then GetVBAEntityName = "AcDbPViewport"
If ent = 36 Then GetVBAEntityName = "AcDbRaster"
If ent = 37 Then GetVBAEntityName = "AcDbRay"
If ent = 38 Then GetVBAEntityName = "AcDbRegion"
If ent = 39 Then GetVBAEntityName = "AcDbShape"
If ent = 40 Then GetVBAEntityName = "AcDbSolid"
If ent = 41 Then GetVBAEntityName = "AcDbSpline"
If ent = 42 Then GetVBAEntityName = "AcDbSubDMesh"
If ent = 43 Then GetVBAEntityName = "AcDbTable"
If ent = 44 Then GetVBAEntityName = "AcDbText"
If ent = 45 Then GetVBAEntityName = "AcDbTolerance"
If ent = 46 Then GetVBAEntityName = "AcDbTrace"
If ent = 47 Then GetVBAEntityName = "AcDbXline"
End Function
Public Function AbrirArchivo(PathFile As Variant)
AutoCAD.Application.Documents.Open (PathFile)
End Function
Public Function ActivarSpace(space As AcActiveSpace)
AutoCAD.Application.ActiveDocument.ActiveSpace = space
End Function
Public Function ContarEntidades(Espacio As Espacios)
If Espacio = 0 Then ContarEntidades = AutoCAD.Application.ActiveDocument.modelspace.Count
If Espacio = 1 Then ContarEntidades = AutoCAD.Application.ActiveDocument.PaperSpace.Count
End Function
Public Function GuardarComo(Path As Variant, Filename As Variant, SaveType As AcSaveAsType)
AutoCAD.Application.ActiveDocument.SaveAs (Path & Filename), SaveType
End Function
Public Function ucs(UcsType As UCSTypes)
If UcsType = 0 Then UcsT = "P"
If UcsType = 1 Then UcsT = "V"
If UcsType = 2 Then UcsT = "W"
AutoCAD.Application.ActiveDocument.SendCommand "_UCS" & vbCr & UcsT & vbCr
End Function

Public Sub Cerrar()
AutoCAD.Application.ActiveDocument.Close
End Sub
Public Sub GridOff()
AutoCAD.Application.ActiveDocument.SendCommand "grid" & vbCr & "of" & vbCr
End Sub
Public Sub Guardar()
AutoCAD.Application.ActiveDocument.Save
End Sub
Public Sub JointAll()
AutoCAD.Application.ActiveDocument.SendCommand "_ai_selall" & vbCr & "_j" & vbCr
End Sub
Public Sub NombreDeEntidad()
Dim entidad As AcadEntity
Set ssetObj = AutoCAD.Application.ActiveDocument.SelectionSets.Add(Rnd)
ssetObj.SelectOnScreen
For Each entidad In ssetObj
MsgBox entidad.ObjectName
Next
ssetObj.Delete
End Sub
Public Function Overkill(torelance As Variant)
AutoCAD.Application.ActiveDocument.SendCommand "-overkill" & vbCr & "all" & vbCr & vbCr & "o" & vbCr & tolerance & vbCr & vbCr
End Function
Public Sub Purge()
AutoCAD.Application.ActiveDocument.PurgeAll
End Sub
Public Sub Regen()
AutoCAD.Application.ActiveDocument.SendCommand "regen" & vbCr
End Sub
Public Sub SelectAll()
AutoCAD.Application.ActiveDocument.SendCommand "_ai_selall" & vbCr
End Sub
Public Sub UnionAllSolids()
AutoCAD.Application.ActiveDocument.SendCommand "_ai_selall" & vbCr & "_union" & vbCr & "all" & vbCr & vbCr
End Sub
Public Sub CopyAllFromZero()
AutoCAD.Application.ActiveDocument.SendCommand "_ai_selall" & vbCr & "_copybase" & vbCr & "0,0,0" & vbCr
End Sub
Public Sub PasteAllAtZero()
AutoCAD.Application.ActiveDocument.SendCommand "_pasteclip " & vbCr & "0,0,0 " & vbCr
End Sub
Public Function Pegar(Punto As String)
AutoCAD.Application.ActiveDocument.SendCommand "_pasteclip " & vbCr & Punto & vbCr
End Function
Public Function Vista(ent As Views)
If ent = 0 Then ObjVBA = "_Top"
If ent = 1 Then ObjVBA = "_Bottom"
If ent = 2 Then ObjVBA = "_Left"
If ent = 3 Then ObjVBA = "_Right"
If ent = 4 Then ObjVBA = "_Front"
If ent = 5 Then ObjVBA = "_Back"
If ent = 6 Then ObjVBA = "_swiso"
If ent = 7 Then ObjVBA = "_seiso"
If ent = 8 Then ObjVBA = "_neiso"
If ent = 9 Then ObjVBA = "_nwiso"
AutoCAD.Application.ActiveDocument.SendCommand "_-view" & vbCr & ObjVBA & vbCr
End Function
Public Function Sombreado(ent As Sombras)
If ent = 0 Then ObjVBA = "2"
If ent = 1 Then ObjVBA = "W"
If ent = 2 Then ObjVBA = "H"
If ent = 3 Then ObjVBA = "_R"
If ent = 4 Then ObjVBA = "_C"
If ent = 5 Then ObjVBA = "S"
If ent = 6 Then ObjVBA = "G"
If ent = 7 Then ObjVBA = "SK"
If ent = 8 Then ObjVBA = "X"
AutoCAD.Application.ActiveDocument.SendCommand "shademode" & vbCr & ObjVBA & vbCr
End Function
Public Function Random(menor As Integer, mayor As Integer)
Random = ((mayor - menor + 1) * Rnd + menor)
Do While Random = 0: Random = ((mayor - menor + 1) * Rnd + menor): Loop 'Non Zero
Do While Random > mayor: Random = ((mayor - menor + 1) * Rnd + menor): Loop 'Non Zero
End Function
Public Function ChangebyDot(value As Variant) As String
value2 = Round(value, 4)
ChangebyDot = Replace(value2, ",", ".")
End Function
Function CurrentFolder() As String
CurrentFolder = AutoCAD.Application.ActiveDocument.Path & "\"
End Function
Function GetBaseName() As String
Dim FSO As New Scripting.FileSystemObject
GetBaseName = FSO.GetBaseName(AutoCAD.Application.ActiveDocument.name)
End Function
Function FilesInFolder()
Dim FSO As New Scripting.FileSystemObject
Dim file As FileSystemObject


Set Files = FSO.GetFolder(CurrentFolder)

For Each file In Files
i = 1 + i

Next
MsgBox i
End Function

Attribute VB_Name = "EngCad_Autocad_Layers"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Dim layerObj As AcadLayer
Public Function Activar(name As Variant)
Set layerObj = AutoCAD.Application.ActiveDocument.Layers.Item(name)
AutoCAD.Application.ActiveDocument.ActiveLayer = layerObj
AutoCAD.Application.ActiveDocument.SendCommand "regen" & vbCr
End Function
Public Function Apagar(name As Variant)
Set layerObj = AutoCAD.Application.ActiveDocument.Layers.Item(nombre)
layerObj.Freeze = True
AutoCAD.Application.ActiveDocument.SendCommand "regen" & vbCr
End Function
Public Function Encender(name As Variant)
Set layerObj = AutoCAD.Application.ActiveDocument.Layers.Item(nombre)
layerObj.Freeze = False
AutoCAD.Application.ActiveDocument.SendCommand "regen" & vbCr
End Function
Public Function Eliminar(name As Variant)
Set layerObj = AutoCAD.Application.ActiveDocument.Layers.Item(nombre)
layerObj.Delete
AutoCAD.Application.ActiveDocument.SendCommand "regen" & vbCr
End Function
Public Function ApagarTodos()
On Error Resume Next
Dim layerObj As AcadLayer
For Each layerObj In AutoCAD.Application.ActiveDocument.Layers
layerObj.Freeze = True
layerObj.LayerOn = False
Next layerObj
AutoCAD.Application.ActiveDocument.SendCommand "regen" & vbCr
End Function
Public Function EncenderTodos()
On Error Resume Next
Dim layerObj As AcadLayer
For Each layerObj In AutoCAD.Application.ActiveDocument.Layers
layerObj.Freeze = False
layerObj.LayerOn = True
Next layerObj
AutoCAD.Application.ActiveDocument.SendCommand "regen" & vbCr
End Function
Public Function layer(nombre As Variant, name As String, Color As Variant, LineType As String, LineWeight As Variant, Plottable As Boolean)
    Set nombre = AutoCAD.Application.ActiveDocument.Layers.Add(name)
    nombre.Color = Color
    nombre.LineType = LineType
    nombre.LineWeight = LineWeight
    nombre.Plottable = Plottable
    nombre = nombre.name
End Function

Public Function nuevo(name As Variant)
Dim NewLayer As AcadLayer
Set NewLayer = AutoCAD.Application.ActiveDocument.Layers.Add(name)
AutoCAD.Application.ActiveDocument.SendCommand "regen" & vbCr
End Function
Public Function NuevoCompleto(name As String, Color As AcColor, LineWeight As AcLineWeight, Plottable As Boolean, Optional LineType As String)
Dim NewLayer As AcadLayer
Set NewLayer = AutoCAD.Application.ActiveDocument.Layers.Add(name)
NewLayer.Color = Color
NewLayer.LineWeight = LineWeight
NewLayer.Plottable = Plottable
NewLayer.name = name
On Error Resume Next
NewLayer.LineType = LineType
End Function
Public Function ApagaExcepto(nombre As Variant)
Dim layerObj As AcadLayer
For Each layerObj In AutoCAD.Application.ActiveDocument.Layers
    If layerObj.name <> nombre Then
    layerObj.Freeze = True
    layerObj.LayerOn = False
    Else
    AutoCAD.Application.ActiveDocument.SendCommand "regen" & vbCr
    End If
Next
End Function
Public Function ActivarLayerAllied(ent As LayersAllied)
If ent = 0 Then ObjVBA = ".3D MODEL"
If ent = 1 Then ObjVBA = ".DIMENSION"
If ent = 2 Then ObjVBA = ".GENERAL ARRANGEMENT"
If ent = 3 Then ObjVBA = ".HIDDEN"
If ent = 4 Then ObjVBA = ".OUTLINE 1"
If ent = 5 Then ObjVBA = ".OUTLINE 3"
If ent = 6 Then ObjVBA = ".TEXT"
If ent = 7 Then ObjVBA = ".TITLE BLOCK ATTRIBUTES"
If ent = 8 Then ObjVBA = ".TITLE BLOCK OUTLINE"
If ent = 9 Then ObjVBA = ".TITLE BLOCK TEXT"
If ent = 10 Then ObjVBA = ".TITLE PAGE OUTLINE"
If ent = 11 Then ObjVBA = "0"
If ent = 12 Then ObjVBA = ".CENTER LINE"
Activar ObjVBA
End Function
Public Sub CargarLayersAlliedPumps()
On Error Resume Next
AutoCAD.Application.ActiveDocument.Linetypes.Load "CENTER", "acad.lin"
AutoCAD.Application.ActiveDocument.Linetypes.Load "HIDDEN", "acad.lin"
layer LayerObj1, ".3D MODEL", acGreen, "Continuous", acLnWt060, True
layer LayerObj1, ".DIMENSION", acMagenta, "Continuous", acLnWt025, True
layer LayerObj2, ".GENERAL ARRANGEMENT", acYellow, "Continuous", acLnWt040, True
layer LayerObj3, ".HIDDEN", 8, "HIDDEN", acLnWt000, True
layer LayerObj4, ".OUTLINE 1", acCyan, "Continuous", acLnWt060, True
layer LayerObj5, ".OUTLINE 3", acRed, "Continuous", acLnWt050, True
layer LayerObj6, ".TEXT", 50, "Continuous", acLnWt030, True
layer LayerObj7, ".TITLE BLOCK ATTRIBUTES", acYellow, "Continuous", acLnWtByLwDefault, True
layer LayerObj8, ".TITLE BLOCK OUTLINE", 151, "Continuous", acLnWtByLwDefault, True
layer LayerObj9, ".TITLE BLOCK TEXT", acGreen, "Continuous", acLnWtByLwDefault, True
layer LayerObj10, ".TITLE PAGE OUTLINE", 252, "Continuous", acLnWtByLwDefault, False
layer LayerObj11, "0", acWhite, "Continuous", acLnWtByLwDefault, True
layer LayerObj12, ".CENTER LINE", 8, "CENTER", acLnWtByLwDefault, True
layer LayerObj13, "Defpoints", acWhite, "Continuous", acLnWtByLwDefault, False
End Sub
Public Sub CargarLayersEntidades2d()
' CARGA UN LAYER PARA CADA ENTIDAD 2D. ESTABLECE COLORES DEL 1 AL 20.
On Error Resume Next
'Entidades 2d
layer LayerObj19, ".Line", 1, "Continuous", acLnWtByLwDefault, True
layer LayerObj23, ".Polyline", 2, "Continuous", acLnWtByLwDefault, True
layer LayerObj23, ".Polyline2d", 3, "Continuous", acLnWtByLwDefault, True
layer LayerObj2, ".Polyline3d", 3, "Continuous", acLnWtByLwDefault, True
layer LayerObj4, ".Arc", 4, "Continuous", acLnWtByLwDefault, True
layer LayerObj8, ".Circle", 5, "Continuous", acLnWtByLwDefault, True
layer LayerObj31, ".Spline", 6, "Continuous", acLnWtByLwDefault, True
layer LayerObj16, ".Ellipse", 9, "Continuous", acLnWtByLwDefault, True
layer LayerObj36, ".Xline", 10, "Continuous", acLnWtByLwDefault, True
layer LayerObj28, ".Region", 11, "Continuous", acLnWtByLwDefault, True
layer LayerObj22, ".Point", 12, "Continuous", acLnWtByLwDefault, True
layer LayerObj17, ".Hatch", 13, "Continuous", acLnWtByLwDefault, True
layer LayerObj21, ".Mtext", 14, "Continuous", acLnWtByLwDefault, True
layer LayerObj32, ".Text", 15, "Continuous", acLnWtByLwDefault, True
layer LayerObj18, ".Leader", 16, "Continuous", acLnWtByLwDefault, True
layer LayerObj48, ".MLeader", 17, "Continuous", acLnWtByLwDefault, True
layer LayerObj40, ".MLine", 18, "Continuous", acLnWtByLwDefault, True
layer LayerObj26, ".Raster", 19, "Continuous", acLnWtByLwDefault, True
layer LayerObj27, ".Ray", 20, "Continuous", acLnWtByLwDefault, True
End Sub
Public Sub CargarLayersEntidades3d()
' CARGA UN LAYER PARA CADA ENTIDAD 3D EN COLORES DEL 21 AL 29.
On Error Resume Next
'Entidades 3d
layer LayerObj1, ".3dFace", 21, "Continuous", acLnWtByLwDefault, True
layer LayerObj3, ".3dSolid", 22, "Continuous", acLnWtByLwDefault, True
layer LayerObj30, ".Solid", 23, "Continuous", acLnWtByLwDefault, True
layer LayerObj29, ".Shape", 24, "Continuous", acLnWtByLwDefault, True
layer LayerObj49, ".SubDMesh", 25, "Continuous", acLnWtByLwDefault, True
layer LayerObj51, ".NurbSurface", 26, "Continuous", acLnWtByLwDefault, True
layer LayerObj50, ".PdfUnderlay", 27, "Continuous", acLnWtByLwDefault, True
layer LayerObj39, ".PolyfaceMesh", 28, "Continuous", acLnWtByLwDefault, True
layer LayerObj25, ".Polymesh", 29, "Continuous", acLnWtByLwDefault, True
End Sub
Public Sub CargarLayersEntidadesMisc()
' CARGA UN LAYER PARA ENTIDADES EN COLORES DEL 30 AL 50.
On Error Resume Next
'Entidades misc
layer LayerObj5, ".Attribute", 30, "Continuous", acLnWtByLwDefault, True
layer LayerObj6, ".AttributeReference", 32, "Continuous", acLnWtByLwDefault, True
layer LayerObj7, ".BlockReference", 33, "Continuous", acLnWtByLwDefault, True
layer LayerObj41, ".Dim3PointAngular", 34, "Continuous", acLnWtByLwDefault, True
layer LayerObj9, ".DimAligned", 35, "Continuous", acLnWtByLwDefault, True
layer LayerObj10, ".DimAngular", 36, "Continuous", acLnWtByLwDefault, True
layer LayerObj44, ".DimArcLength", 37, "Continuous", acLnWtByLwDefault, True
layer LayerObj12, ".DimDiametric", 38, "Continuous", acLnWtByLwDefault, True
layer LayerObj13, ".DimOrdinate", 39, "Continuous", acLnWtByLwDefault, True
layer LayerObj14, ".DimRadial", 40, "Continuous", acLnWtByLwDefault, True
layer LayerObj45, ".DimRadialLarge", 41, "Continuous", acLnWtByLwDefault, True
layer LayerObj15, ".DimRotated", 42, "Continuous", acLnWtByLwDefault, True
layer LayerObj46, ".DwfUnderlay", 43, "Continuous", acLnWtByLwDefault, True
layer LayerObj42, ".ExternalReference", 44, "Continuous", acLnWtByLwDefault, True
layer LayerObj43, ".Table", 45, "Continuous", acLnWtByLwDefault, True
layer LayerObj33, ".Tolerance", 46, "Continuous", acLnWtByLwDefault, True
layer LayerObj34, ".Trace", 47, "Continuous", acLnWtByLwDefault, True
layer LayerObj47, ".DgnUnderlay", 48, "Continuous", acLnWtByLwDefault, True
layer LayerObj35, ".PViewport", 49, "Continuous", acLnWtByLwDefault, True
layer LayerObj38, ".MInsertBlock", 50, "Continuous", acLnWtByLwDefault, True
End Sub
Public Sub CargarLayersTodasEntidadesPosibles()
' CARGA LAYERS PARA TODAS LAS ENTIDADES Y ESTABLECE COLORES DEL 1 AL 50.
On Error Resume Next
'Todas las Entidades
layer LayerObj19, ".Line", 1, "Continuous", acLnWtByLwDefault, True
layer LayerObj23, ".Polyline", 2, "Continuous", acLnWtByLwDefault, True
layer LayerObj23, ".Polyline2d", 3, "Continuous", acLnWtByLwDefault, True
layer LayerObj2, ".Polyline3d", 3, "Continuous", acLnWtByLwDefault, True
layer LayerObj4, ".Arc", 4, "Continuous", acLnWtByLwDefault, True
layer LayerObj8, ".Circle", 5, "Continuous", acLnWtByLwDefault, True
layer LayerObj31, ".Spline", 6, "Continuous", acLnWtByLwDefault, True
layer LayerObj16, ".Ellipse", 9, "Continuous", acLnWtByLwDefault, True
layer LayerObj36, ".Xline", 10, "Continuous", acLnWtByLwDefault, True
layer LayerObj28, ".Region", 11, "Continuous", acLnWtByLwDefault, True
layer LayerObj22, ".Point", 12, "Continuous", acLnWtByLwDefault, True
layer LayerObj17, ".Hatch", 13, "Continuous", acLnWtByLwDefault, True
layer LayerObj21, ".Mtext", 14, "Continuous", acLnWtByLwDefault, True
layer LayerObj32, ".Text", 15, "Continuous", acLnWtByLwDefault, True
layer LayerObj18, ".Leader", 16, "Continuous", acLnWtByLwDefault, True
layer LayerObj48, ".MLeader", 17, "Continuous", acLnWtByLwDefault, True
layer LayerObj40, ".MLine", 18, "Continuous", acLnWtByLwDefault, True
layer LayerObj26, ".Raster", 19, "Continuous", acLnWtByLwDefault, True
layer LayerObj27, ".Ray", 20, "Continuous", acLnWtByLwDefault, True
layer LayerObj1, ".3dFace", 21, "Continuous", acLnWtByLwDefault, True
layer LayerObj3, ".3dSolid", 22, "Continuous", acLnWtByLwDefault, True
layer LayerObj30, ".Solid", 23, "Continuous", acLnWtByLwDefault, True
layer LayerObj29, ".Shape", 24, "Continuous", acLnWtByLwDefault, True
layer LayerObj49, ".SubDMesh", 25, "Continuous", acLnWtByLwDefault, True
layer LayerObj51, ".NurbSurface", 26, "Continuous", acLnWtByLwDefault, True
layer LayerObj50, ".PdfUnderlay", 27, "Continuous", acLnWtByLwDefault, True
layer LayerObj39, ".PolyfaceMesh", 28, "Continuous", acLnWtByLwDefault, True
layer LayerObj25, ".Polymesh", 29, "Continuous", acLnWtByLwDefault, True
layer LayerObj5, ".Attribute", 30, "Continuous", acLnWtByLwDefault, True
layer LayerObj6, ".AttributeReference", 32, "Continuous", acLnWtByLwDefault, True
layer LayerObj7, ".BlockReference", 33, "Continuous", acLnWtByLwDefault, True
layer LayerObj41, ".Dim3PointAngular", 34, "Continuous", acLnWtByLwDefault, True
layer LayerObj9, ".DimAligned", 35, "Continuous", acLnWtByLwDefault, True
layer LayerObj10, ".DimAngular", 36, "Continuous", acLnWtByLwDefault, True
layer LayerObj44, ".DimArcLength", 37, "Continuous", acLnWtByLwDefault, True
layer LayerObj12, ".DimDiametric", 38, "Continuous", acLnWtByLwDefault, True
layer LayerObj13, ".DimOrdinate", 39, "Continuous", acLnWtByLwDefault, True
layer LayerObj14, ".DimRadial", 40, "Continuous", acLnWtByLwDefault, True
layer LayerObj45, ".DimRadialLarge", 41, "Continuous", acLnWtByLwDefault, True
layer LayerObj15, ".DimRotated", 42, "Continuous", acLnWtByLwDefault, True
layer LayerObj46, ".DwfUnderlay", 43, "Continuous", acLnWtByLwDefault, True
layer LayerObj42, ".ExternalReference", 44, "Continuous", acLnWtByLwDefault, True
layer LayerObj43, ".Table", 45, "Continuous", acLnWtByLwDefault, True
layer LayerObj33, ".Tolerance", 46, "Continuous", acLnWtByLwDefault, True
layer LayerObj34, ".Trace", 47, "Continuous", acLnWtByLwDefault, True
layer LayerObj47, ".DgnUnderlay", 48, "Continuous", acLnWtByLwDefault, True
layer LayerObj35, ".PViewport", 49, "Continuous", acLnWtByLwDefault, True
layer LayerObj38, ".MInsertBlock", 50, "Continuous", acLnWtByLwDefault, True
End Sub

Attribute VB_Name = "Entidades"
Dim entidad As AcadEntity
Dim ly As New EngCad_Autocad_Layers
Dim acad As New EngCad_Autocad_General
Dim acadedit As New EngCad_Autocad_Edition
Public Sub DameNombreEntidad() '^C^C-vbarun DameNombreEntidad
Set ssetObj = AutoCAD.Application.ActiveDocument.SelectionSets.Add(Rnd)
ssetObj.SelectOnScreen
For Each entidad In ssetObj
MsgBox entidad.ObjectName
Next
ssetObj.Delete
End Sub
Sub ContarEntidades() '^C^C-vbarun ContarEntidades
MsgBox AutoCAD.Application.ActiveDocument.modelspace.Count & " entities."
End Sub
Public Sub AislarEntidadesPorLayers() '^C^C-vbarun AislarEntidadesPorLayers
Call Load_Entities_Layers_All
'Primer Grupo
For Each entidad In AutoCAD.Application.ActiveDocument.modelspace
If entidad.ObjectName = "AcDbLine" Then entidad.layer = ".Line"
If entidad.ObjectName = "AcDb2dPolyline" Then entidad.layer = ".Polyline2d"
If entidad.ObjectName = "AcDbLWPolyline" Then entidad.layer = ".Polyline"
If entidad.ObjectName = "AcDb3dPolyline" Then entidad.layer = ".Polyline"
If entidad.ObjectName = "AcDbPolyline" Then entidad.layer = ".Polyline"
If entidad.ObjectName = "AcDbArc" Then entidad.layer = ".Arc"
If entidad.ObjectName = "AcDbCircle" Then entidad.layer = ".Circle"
If entidad.ObjectName = "AcDbSpline" Then entidad.layer = ".Spline"
If entidad.ObjectName = "AcDbEllipse" Then entidad.layer = ".Ellipse"
If entidad.ObjectName = "AcDbXline" Then entidad.layer = ".Xline"
If entidad.ObjectName = "AcDbRegion" Then entidad.layer = ".Region"
If entidad.ObjectName = "AcDbPoint" Then entidad.layer = ".Point"
If entidad.ObjectName = "AcDbHatch" Then entidad.layer = ".Hatch"
If entidad.ObjectName = "AcDbMtext" Then entidad.layer = ".Mtext"
If entidad.ObjectName = "AcDbText" Then entidad.layer = ".Text"
If entidad.ObjectName = "AcDbLeader" Then entidad.layer = ".Leader"
If entidad.ObjectName = "AcDbMLeader" Then entidad.layer = ".MLeader"
If entidad.ObjectName = "AcDbMLine" Then entidad.layer = ".MLine"
If entidad.ObjectName = "AcDbRaster" Then entidad.layer = ".Raster"
If entidad.ObjectName = "AcDbRay" Then entidad.layer = ".Ray"
Next
acad.Purge
End Sub
Sub Overkill_Ent_Select() '^C^C-vbarun Overkill_Ent_Select
acadedit.BorrarSelectionSets
Set ssetObj = AutoCAD.Application.ActiveDocument.SelectionSets.Add(Rnd): ssetObj.SelectOnScreen
For Each entidad In ssetObj
ActualLayer = entidad.layer
namelayer = "random" & entidad.ObjectID
ly.nuevo namelayer: ly.Activar namelayer: entidad.layer = namelayer: ly.ApagaExcepto namelayer
AutoCAD.Application.ActiveDocument.SendCommand "-overkill" & vbCr & "all" & vbCr & vbCr & "f" & vbCr & "0" & vbCr & vbCr
Next
ly.EncenderTodos
ly.Activar "0"
AislarEntidadesPorLayers
ssetObj.Delete
End Sub
Sub Overkill_All_Ent_by_Select() '^C^C-vbarun Overkill_All_Ent_by_Select
acadedit.BorrarSelectionSets
Set ssetObj = AutoCAD.Application.ActiveDocument.SelectionSets.Add(Rnd): ssetObj.SelectOnScreen
For Each entidad In ssetObj: EntityType = entidad.ObjectName: Exit For: Next: ssetObj.Delete
For Each entidad In AutoCAD.Application.ActiveDocument.modelspace
If entidad.ObjectName = EntityType Then
namelayer = "random" & entidad.ObjectID
ly.nuevo namelayer: ly.Activar namelayer: entidad.layer = namelayer: ly.ApagaExcepto namelayer
AutoCAD.Application.ActiveDocument.SendCommand "-overkill" & vbCr & "all" & vbCr & vbCr & "f" & vbCr & "0" & vbCr & vbCr
ly.EncenderTodos
ly.Activar "0"
AislarEntidadesPorLayers
Else:
End If
Next
End Sub
Sub Overkill_All_Ent() '^C^C-vbarun Overkill_All_Ent_by_Select
On Error Resume Next
For Each entidad In AutoCAD.Application.ActiveDocument.modelspace
namelayer = "random" & entidad.ObjectID
ly.nuevo namelayer: ly.Activar namelayer: entidad.layer = namelayer: ly.ApagaExcepto namelayer
AutoCAD.Application.ActiveDocument.SendCommand "-overkill" & vbCr & "all" & vbCr & vbCr & "f" & vbCr & "0" & vbCr & vbCr
ly.EncenderTodos
Next
ly.Activar "0"
AislarEntidadesPorLayers
End Sub
Sub Joint_All_Entities() '^C^C-vbarun Joint_All_Entities
AutoCAD.Application.ActiveDocument.SendCommand "PEDIT" & vbCr & "M" & vbCr & "all" & vbCr & vbCr & vbCr & "j" & vbCr & vbCr & vbCr
ly.Activar "0"
AislarEntidadesPorLayers
ZoomExtents
AutoCAD.Application.ActiveDocument.SendCommand "grid" & vbCr & "off" & vbCr & "snap" & vbCr & "off" & vbCr
End Sub

Attribute VB_Name = "Gables"
Sub fixDxf()
Overkill_All_Ent

Convert_Poly_to_Poly2d_All

AislarLineasGrandes


End Sub

Attribute VB_Name = "Layers"
Dim ly As New EngCad_Autocad_Layers
Public Sub Load_Entities_Layers_2D() '^C^C-vbarun Load_Entities_Layers_2D
ly.CargarLayersEntidades2d
End Sub
Public Sub Load_Entities_Layers_3D() '^C^C-vbarun Load_Entities_Layers_3D
ly.CargarLayersEntidades3d
End Sub
Public Sub Load_Entities_Layers_Misc() '^C^C-vbarun Load_Entities_Layers_Misc
ly.CargarLayersEntidadesMisc
End Sub
Public Sub Load_Entities_Layers_All() '^C^C-vbarun Load_Entities_Layers_All
ly.CargarLayersTodasEntidadesPosibles
End Sub
Public Sub Load_Allied_Layers() '^C^C-vbarun Load_Allied_Layers
ly.CargarLayersAlliedPumps
End Sub

Attribute VB_Name = "Lotes"
' Abrir archivo donde esta la carpeta
' seleccionar proceso
Dim ly As New EngCad_Autocad_Layers
Dim acad As New EngCad_Autocad_General
Dim acadedit As New EngCad_Autocad_Edition
Dim acaddraw As New EngCad_Autocad_Draw

Dim entidad As AcadEntity
Dim i As Integer
Dim modelspace As AcadModelSpace
Dim PaperSpace As AcadPaperSpace
Dim ssetObj As AcadSelectionSet
Dim layerObj As AcadLayer
Dim LayerCol As AcadLayers
Dim linea As AcadLine
Dim Poly As AcadPolyline
Dim Poly1 As AcadLWPolyline
Dim Poly2 As Acad3DPolyline
Dim spl As AcadSpline
Dim line As AcadLine

Sub ProcesoPorLotes() '^C^C-vbarun ProcesoPorLotes
Dim file As Variant
Dim FSO As New FileSystemObject
Dim Ruta As String
Ruta_Archivos = AutoCAD.Application.ActiveDocument.Path & "\"
Set Archivos = FSO.GetFolder(Ruta_Archivos)
UserForm1.Show
acad.Cerrar
On Error Resume Next
FSO.CreateFolder (Ruta_Archivos & UserForm1.ComboBox1.value)
Ruta_Archivos2 = Ruta_Archivos & UserForm1.ComboBox1.value & "\"
For Each file In Archivos.Files
ShortName = FSO.GetBaseName(file) & " (" & UserForm1.ComboBox1.value & ")"
ShortName = FSO.GetBaseName(file)
acad.AbrirArchivo (FSO.GetAbsolutePathName(file))
Call ProcessToApply
ZoomExtents
AutoCAD.Application.ActiveDocument.SaveAs Ruta_Archivos2 & ShortName, ac2000_dxf
AutoCAD.Application.ActiveDocument.Close
Next
End Sub

Sub ProcessToApply()
If UserForm1.ComboBox1.value = "Overkill All" Then Call Overkill_All_Ent
If UserForm1.ComboBox1.value = "Convert Poly to Poly2d" Then Call Convert_Poly_to_Poly2d_All




End Sub
Sub AislarLineasGrandes()
'AISLANDO LA POLILINEA MAS GRANDE
'Agrega en la variable maxval el perimetro de la polilinea mas grande.
maxval = 0: Set MS = AutoCAD.Application.ActiveDocument.modelspace
For Each entidad In MS
If entidad.ObjectName = "AcDb2dPolyline" Then
Set Poly = entidad
If maxval < Poly.Length Then maxval = Poly.Length
Else
End If
Next
'Aislando a un layer nuevo la polilinea mas grande.
For Each entidad In MS
If entidad.ObjectName = "AcDb2dPolyline" Then
Set Poly = entidad
If Poly.Length = maxval Then
namelayer = "random" & Poly.ObjectID: ly.nuevo namelayer: ly.Activar namelayer: Poly.layer = namelayer: ly.ApagaExcepto namelayer
Else
End If
Else
End If
Next
'Explotando la polilinea.
ZoomExtents
AutoCAD.Application.ActiveDocument.SendCommand "_ai_selall" & vbCr & "EXPLODE" & vbCr
'Repite el codigo dos veces porque se buscan dos lineas
'Agrega en la variable maxval el largo de la linea mas grande.
For x = 1 To 2
maxval = 0
For Each entidad In AutoCAD.Application.ActiveDocument.modelspace
If entidad.ObjectName = "AcDbLine" Then
If entidad.layer = namelayer Then
Set line = entidad
If maxval < line.Length Then maxval = line.Length
Else
End If
Else
End If
Next
'Moviendo la linea mas grande al layer ".linea"
For Each entidad In AutoCAD.Application.ActiveDocument.modelspace
If entidad.ObjectName = "AcDbLine" Then
Set line = entidad
If line.Length = maxval Then
line.layer = ".Line"
Else
End If
Else
End If
Next
Next
'Una vez aisladas las lineas al layer ".linea" el resto es unido a una nueva polilinea.
AutoCAD.Application.ActiveDocument.SendCommand "PEDIT" & vbCr & "M" & vbCr & "all" & vbCr & vbCr & vbCr & "j" & vbCr & vbCr & vbCr
AutoCAD.Application.ActiveDocument.SendCommand "PEDIT" & vbCr & "M" & vbCr & "all" & vbCr & vbCr & "F" & vbCr & vbCr
ly.EncenderTodos: ly.Activar "0": AislarEntidadesPorLayers
acadedit.SelectAndDelete -0.005, -0.005, 0.005, 0.005, LoQueEncierra

'Borrar basura
For Each entidad In MS
If entidad.layer = ".Line" Then
Set linea = entidad
'MsgBox linea.Length
If Round(linea.Length, 4) <= 0 Then linea.Delete
Else
End If
Next

'Reemplazar lineas
For Each entidad In MS
If entidad.layer = ".Line" Then
Set linea = entidad
If Math.Abs(linea.StartPoint(0)) < Math.Abs(linea.EndPoint(0)) Then
acaddraw.linea acModelSpace, 0, 0, 0, linea.EndPoint(0), linea.EndPoint(1), 0, acByLayer, ".Line"
Else
acaddraw.linea acModelSpace, 0, 0, 0, linea.StartPoint(0), linea.StartPoint(1), 0, acByLayer, ".Line"
End If
linea.Delete
Else
End If
Next

End Sub
Sub sdfs()

AislarlaMasgrande AcDb2dPolyline
End Sub

Public Function AislarlaMasgrande(ent As EngCadEntityName)
maxval = 0: Set MS = AutoCAD.Application.ActiveDocument.modelspace
realname = acad.EnumToStringEngCadEntityName(ent)
For Each entidad In MS
If entidad.ObjectName = realname Then
Set Poly = entidad
If maxval < Poly.Length Then maxval = Poly.Length
Else
End If
Next
For Each entidad In MS
If entidad.ObjectName = realname Then
Set Poly = entidad
If Poly.Length = maxval Then
namelayer = "random" & Poly.ObjectID: ly.nuevo namelayer: ly.Activar namelayer: Poly.layer = namelayer: ly.ApagaExcepto namelayer
Else
End If
Else
End If
Next
End Function

Function MoverInicioLineas(linea As AcadLine)
If Math.Abs(linea.StartPoint(0)) < Math.Abs(linea.EndPoint(0)) Then
acaddraw.linea acModelSpace, 0, 0, 0, linea.EndPoint(0), linea.EndPoint(1), 0
Else
acaddraw.linea acModelSpace, 0, 0, 0, linea.StartPoint(0), linea.StartPoint(1), 0
End If
linea.Delete
End Function

'voy a crar un array de objectos de autocad entidades
'despues lo voy a llamar como argumento y voy a leer propiedades

Function ArrayOfAcadEntities(space As AcActiveSpace, entity As AcEntityName)

If space = 1 Then Set spacegroup = AutoCAD.Application.ActiveDocument.modelspace


Dim arr()

Dim entidad As AcadEntity
i = 0
For Each entidad In spacegroup
i = i + 1
ReDim Preserve arr(0 To i)

arr(i) = entidad

Next
ArrayOfAcadEntities = arr()
End Function






''
'Sub FilesInFolder()
''Dim MyObj As Object, Convert As Object
'Dim file As Variant
'Dim FSO As New FileSystemObject
'Dim Ruta As String
'Ruta_Archivos = AutoCAD.application.ActiveDocument.Path
'Set Archivos = FSO.GetFolder(Ruta_Archivos)
'For Each file In Archivos.files
''Filename = file.Name
'
'i = i + 1
'
'Next
'MsgBox i
'End Sub
'Sub ListarNombresArchivos()
'Dim MyObj As Object, Convert As Object, file As Variant
'Dim FSO As New FileSystemObject
'Dim Ruta As String
'
''se Debe Activar Microsoft Scripting Runtime
'
''seleccionar ruta donde se encuentran los archivos a listar, escriba un nombre para el archivo txt.
''a continuación se creará un archivo txt con los nombres de los archivos.
'
'Ruta_Archivos = AutoCAD.application.ActiveDocument.Path
'
'nombre = "nuevo"
'NotepadFile = Ruta_Archivos & nombre & ".txt"
'FSO.CreateTextFile NotepadFile, True
'Set Archivos = FSO.GetFolder(Ruta_Archivos)
'Open NotepadFile For Output As #1
'For Each file In Archivos.files
'
'Filename = file.Name
'
'Print #1, Filename
'Next
'Close #1
'
'End Sub

Attribute VB_Name = "Module1"
Sub ListarNombresArchivos()
Dim MyObj As Object, Convert As Object, file As Variant
Dim FSO As New FileSystemObject
Dim Path  As String

Path = "C:\1\"

Set Font = FSO.GetFolder(Path)
For Each file In Font.Files


FSO.CopyFile Path & file.name, Path & FSO.GetBaseName(file) & ".csv"

Next

End Sub

Attribute VB_Name = "Polylineas2d"
Dim ly As New EngCad_Autocad_Layers
Dim acad As New EngCad_Autocad_General
Dim acadedit As New EngCad_Autocad_Edition

Dim entidad As AcadEntity
Dim i As Integer
Dim modelspace As AcadModelSpace
Dim PaperSpace As AcadPaperSpace
Dim ssetObj As AcadSelectionSet
Dim layerObj As AcadLayer
Dim LayerCol As AcadLayers
Dim linea As AcadLine
Dim Poly As AcadPolyline
Dim Poly1 As AcadLWPolyline
Dim Poly2 As Acad3DPolyline
Dim spl As AcadSpline
Sub SetAll_Poly2d_None() '^C^C-vbarun SetAll_Poly2d_None
Change_Fit_Smooth acSimplePoly
End Sub
Sub SetAll_Poly2d_Curve_Fit() '^C^C-vbarun SetAll_Poly2d_Curve_Fit
Change_Fit_Smooth acFitCurvePoly
End Sub
Sub SetAll_Poly2d_Quadratic() '^C^C-vbarun SetAll_Poly2d_Quadratic
Change_Fit_Smooth acQuadSplinePoly
End Sub
Sub SetAll_Poly2d_Cubic() '^C^C-vbarun SetAll_Poly2d_Cubic
Change_Fit_Smooth acCubicSplinePoly
End Sub
Function Change_Fit_Smooth(mode As Variant)
For Each entidad In AutoCAD.Application.ActiveDocument.modelspace
If entidad.ObjectName = "AcDb2dPolyline" Then
Set Poly = entidad
Poly.Type = mode
Else
End If
Next
End Function
Sub Convert_Poly2d_to_Poly_Select() 'Autocad 2007 - Funciona
acadedit.BorrarSelectionSets
Set ssetObj = AutoCAD.Application.ActiveDocument.SelectionSets.Add(Rnd): ssetObj.SelectOnScreen
For Each entidad In ssetObj
If entidad.ObjectName = "AcDb2dPolyline" Then
namelayer = "random" & entidad.ObjectID: ly.nuevo namelayer: ly.Activar namelayer: entidad.layer = namelayer: ly.ApagaExcepto namelayer
AutoCAD.Application.ActiveDocument.SendCommand "_ai_selall" & vbCr & "EXPLODE" & vbCr
AutoCAD.Application.ActiveDocument.SendCommand "PEDIT" & vbCr & "M" & vbCr & "all" & vbCr & vbCr & vbCr & "j" & vbCr & vbCr & vbCr
Else
MsgBox "La selección no es una Polilinea 2d."
Exit Sub
End If
Next
ly.EncenderTodos: ly.Activar "0": AislarEntidadesPorLayers: ssetObj.Delete 'restore selection
End Sub
Sub Convert_Poly2d_to_Poly_ALL()
ZoomExtents
For Each entidad In AutoCAD.Application.ActiveDocument.modelspace
If entidad.ObjectName = "AcDb2dPolyline" Then
namelayer = "random" & entidad.ObjectID: ly.nuevo namelayer: ly.Activar namelayer: entidad.layer = namelayer: ly.ApagaExcepto namelayer
AutoCAD.Application.ActiveDocument.SendCommand "_ai_selall" & vbCr & "EXPLODE" & vbCr
AutoCAD.Application.ActiveDocument.SendCommand "PEDIT" & vbCr & "M" & vbCr & "all" & vbCr & vbCr & vbCr & "j" & vbCr & vbCr & vbCr
ly.EncenderTodos: ly.Activar "0"
Else
End If
Next
ly.EncenderTodos: ly.Activar "0": AislarEntidadesPorLayers 'restore all
End Sub
Sub Convert_Poly2d_to_Spline_Select() '^C^C-vbarun Convert_Poly2d_to_Spline_Select
acadedit.BorrarSelectionSets
Set ssetObj = AutoCAD.Application.ActiveDocument.SelectionSets.Add(Rnd): ssetObj.SelectOnScreen
For Each entidad In ssetObj
If entidad.ObjectName = "AcDb2dPolyline" Then
'Change Fit/Smooth to Spline: acCubicSplinePoly
Set Poly = entidad: Poly.Type = acCubicSplinePoly
'Convert to Spline
namelayer = "random" & entidad.ObjectID: ly.nuevo namelayer: ly.Activar namelayer: entidad.layer = namelayer: ly.ApagaExcepto namelayer
AutoCAD.Application.ActiveDocument.SendCommand "_ai_selall" & vbCr & "SPLINEDIT" & vbCr & vbCr
Else
MsgBox "La selección no es una Polilinea 2d."
Exit Sub
End If
Next
ly.EncenderTodos: ly.Activar "0": AislarEntidadesPorLayers: ssetObj.Delete 'restore selection
End Sub
Sub Convert_Poly2d_to_Spline_All() '^C^C-vbarun Convert_Poly2d_to_Spline_All
ZoomExtents
On Error Resume Next
For Each entidad In AutoCAD.Application.ActiveDocument.modelspace
If entidad.ObjectName = "AcDb2dPolyline" Then
'Change Fit/Smooth to Spline: acCubicSplinePoly
Set Poly = entidad: Poly.Type = acCubicSplinePoly
'Convert to Spline
namelayer = "random" & entidad.ObjectID: ly.nuevo namelayer: ly.Activar namelayer: entidad.layer = namelayer: ly.ApagaExcepto namelayer
AutoCAD.Application.ActiveDocument.SendCommand "_ai_selall" & vbCr & "SPLINEDIT" & vbCr & vbCr
ly.EncenderTodos
Else
End If
Next
ly.EncenderTodos: ly.Activar "0": AislarEntidadesPorLayers 'restore all
End Sub

Attribute VB_Name = "Polylines"
Dim ly As New EngCad_Autocad_Layers
Dim acad As New EngCad_Autocad_General
Dim acadedit As New EngCad_Autocad_Edition

Dim entidad As AcadEntity
Dim i As Integer
Dim modelspace As AcadModelSpace
Dim PaperSpace As AcadPaperSpace
Dim ssetObj As AcadSelectionSet
Dim layerObj As AcadLayer
Dim LayerCol As AcadLayers
Dim linea As AcadLine
Dim Poly As AcadPolyline
Dim Poly1 As AcadLWPolyline
Dim Poly2 As Acad3DPolyline
Dim spl As AcadSpline


Sub Convert_Poly_to_Poly2d_Select()
acad.BorrarSelectionSets
Set ssetObj = AutoCAD.Application.ActiveDocument.SelectionSets.Add(Rnd): ssetObj.SelectOnScreen
For Each entidad In ssetObj
If entidad.ObjectName = "AcDbPolyline" Then
namelayer = "random" & entidad.ObjectID: ly.nuevo namelayer: ly.Activar namelayer: entidad.layer = namelayer: ly.ApagaExcepto namelayer
AutoCAD.Application.ActiveDocument.SendCommand "PEDIT" & vbCr & "M" & vbCr & "all" & vbCr & vbCr & "F" & vbCr & vbCr
Else
MsgBox "La selección no es una Polilinea."
Exit Sub
End If
Next
ly.EncenderTodos: ly.Activar "0": AislarEntidadesPorLayers: ssetObj.Delete 'restore selection
End Sub

Sub Convert_Poly_to_Poly2d_All()
For Each entidad In AutoCAD.Application.ActiveDocument.modelspace
If entidad.ObjectName = "AcDbPolyline" Then
namelayer = "random" & entidad.ObjectID: ly.nuevo namelayer: ly.Activar namelayer: entidad.layer = namelayer: ly.ApagaExcepto namelayer
AutoCAD.Application.ActiveDocument.SendCommand "PEDIT" & vbCr & "M" & vbCr & "all" & vbCr & vbCr & "F" & vbCr & vbCr
ly.EncenderTodos: ly.Activar "0"
Else
End If
Next
SetAll_Poly2d_None
ly.EncenderTodos: ly.Activar "0": AislarEntidadesPorLayers 'restore all
End Sub

Attribute VB_Name = "Spiral"
Dim ly As New EngCad_Autocad_Layers
Dim acad As New EngCad_Autocad_General
Dim acadedit As New EngCad_Autocad_Edition
Dim draw As New EngCad_Autocad_Draw
Dim entidad As AcadEntity
Dim Entidad2 As AcadEntity
Dim i As Integer
Dim modelspace As AcadModelSpace
Dim PaperSpace As AcadPaperSpace
Dim ssetObj As AcadSelectionSet
Dim layerObj As AcadLayer
Dim LayerCol As AcadLayers
Dim LineaNew As AcadLine
Dim Poly As AcadPolyline
Dim Poly1 As AcadLWPolyline
Dim Poly2 As Acad3DPolyline
Dim spl As AcadSpline

Sub Espiral() '^C^C-vbarun Espiral
'MACRO INTERACTIVA
acadedit.NuevoDibujo
ly.CargarLayersAlliedPumps
'Request variables by prompt:
pnt1 = AutoCAD.Application.ActiveDocument.Utility.GetPoint(, "First point: ")
pnt2 = AutoCAD.Application.ActiveDocument.Utility.GetPoint(, "Second point: ")
rad1 = AutoCAD.Application.ActiveDocument.Utility.GetDistance(pnt1, "First radious: ")
rad2 = AutoCAD.Application.ActiveDocument.Utility.GetDistance(pnt2, "Second radious: ")
thk = AutoCAD.Application.ActiveDocument.Utility.GetDistance(pnt2, "Thick: ")
'fac = AutoCAD.Application.ActiveDocument.Utility.GetReal("Coef <1.26>: ")
'rep = AutoCAD.Application.ActiveDocument.Utility.GetReal("Loops <4>: ")
ly.ActivarLayerAllied CENTER_LINE
'draw.Circulo acModelSpace, pnt1(0), pnt1(1), pnt1(2), rad1, acByLayer
'draw.Circulo acModelSpace, pnt2(0), pnt2(1), pnt2(2), rad2, acByLayer
'Linea lineafunction, pnt1(0), pnt1(1), pnt1(2), pnt2(0), pnt2(1), pnt2(2) 'linea de eje
Dim PuntoA(0 To 2) As Double: Dim PuntoB(0 To 2) As Double: Dim anguloejecentros As Double
PuntoA(0) = pnt1(0):     PuntoA(1) = pnt1(1):         PuntoA(2) = pnt1(2)
PuntoB(0) = pnt2(0):     PuntoB(1) = pnt2(1):         PuntoB(2) = pnt2(2)
Set LineaNew = AutoCAD.Application.ActiveDocument.modelspace.AddLine(PuntoA, PuntoB)
anguloejecentros = LineaNew.Angle
LineaNew.Delete
ConsoleCptA = acad.ChangebyDot(pnt1(0)) & "," & acad.ChangebyDot(pnt1(1))
ConsoleCptB = acad.ChangebyDot(pnt2(0)) & "," & acad.ChangebyDot(pnt2(1))
Angle = ((180 * anguloejecentros) / 3.14159265358979) * -1
Rotation = acad.ChangebyDot(Angle)
fac = 1.26: rep = 4
r0 = rad1:    r1 = r0 / fac
ly.nuevo "Temporal1": ly.nuevo "Temporal2"
ly.ActivarLayerAllied GENERAL_ARRANGEMENT
namelayer = "random" & Round(Rnd * 1000, 0): ly.nuevo namelayer: ly.Activar namelayer: ly.ApagaExcepto namelayer
For i = 1 To rep
    r0 = rad1:    r1 = r0 / fac:    r2 = r1 / fac:    r3 = r2 / fac:    r4 = r3 / fac
    radarc1 = ((r0 - r1) / 2) + r1:    radarc2 = ((r1 - r2) / 2) + r2
    radarc3 = ((r2 - r3) / 2) + r3:    radarc4 = ((r3 - r4) / 2) + r4
    'If i <= 1 Then Linea 1, pnt1(0), pnt1(1), pnt1(2), pnt1(0), pnt1(1) + r0, pnt1(2)
    ArcFromConsole pnt1(0), pnt1(1) + r0, pnt1(2), pnt1(0) - r1, pnt1(1), pnt1(2), radarc1
    ArcFromConsole pnt1(0) - r1, pnt1(1), pnt1(2), pnt1(0), pnt1(1) - r2, pnt1(2), radarc2
    ArcFromConsole pnt1(0), pnt1(1) - r2, pnt1(2), pnt1(0) + r3, pnt1(1), pnt1(2), radarc3
    ArcFromConsole pnt1(0) + r3, pnt1(1), pnt1(2), pnt1(0), pnt1(1) + r4, pnt1(2), radarc4
    rad1 = r4
Next
AutoCAD.Application.ActiveDocument.SendCommand "PEDIT" & vbCr & "M" & vbCr & "all" & vbCr & vbCr & vbCr & "j" & vbCr & vbCr & vbCr
AutoCAD.Application.ActiveDocument.SendCommand "ro" & vbCr & "all" & vbCr & vbCr & ConsoleCptA & vbCr & Rotation & vbCr
For Each entidad In AutoCAD.Application.ActiveDocument.modelspace
    If entidad.ObjectName = "AcDbPolyline" Then
        If entidad.layer = namelayer Then
        Set Poly1 = entidad
        x1 = Poly1.Coordinates(0): y1 = Poly1.Coordinates(1)
        Else
        End If
    Else
    End If
Next

ly.EncenderTodos: ly.Activar "0" 'restore all
NameLayer2 = "random" & Round(Rnd * 1000, 0): ly.nuevo NameLayer2: ly.Activar NameLayer2: ly.ApagaExcepto NameLayer2
For i = 1 To rep
    r0 = rad2:    r1 = r0 / fac:    r2 = r1 / fac:    r3 = r2 / fac:    r4 = r3 / fac
    radarc1 = ((r0 - r1) / 2) + r1:    radarc2 = ((r1 - r2) / 2) + r2
    radarc3 = ((r2 - r3) / 2) + r3:    radarc4 = ((r3 - r4) / 2) + r4
    'If i <= 1 Then Linea 3, pnt2(0), pnt2(1), pnt2(2), pnt2(0), pnt2(1) - r0, pnt2(2)
    ArcFromConsole pnt2(0), pnt2(1) - r0, pnt2(2), pnt2(0) + r1, pnt2(1), pnt2(2), radarc1
    ArcFromConsole pnt2(0) + r1, pnt2(1), pnt2(2), pnt2(0), pnt2(1) + r2, pnt2(2), radarc2
    ArcFromConsole pnt2(0), pnt2(1) + r2, pnt2(2), pnt2(0) - r3, pnt2(1), pnt2(2), radarc3
    ArcFromConsole pnt2(0) - r3, pnt2(1), pnt2(2), pnt2(0), pnt2(1) - r4, pnt2(2), radarc4
    rad2 = r4
Next
AutoCAD.Application.ActiveDocument.SendCommand "PEDIT" & vbCr & "M" & vbCr & "all" & vbCr & vbCr & vbCr & "j" & vbCr & vbCr & vbCr
AutoCAD.Application.ActiveDocument.SendCommand "ro" & vbCr & "all" & vbCr & vbCr & ConsoleCptB & vbCr & Rotation & vbCr
For Each entidad In AutoCAD.Application.ActiveDocument.modelspace
    If entidad.ObjectName = "AcDbPolyline" Then
        If entidad.layer = NameLayer2 Then
        Set Poly1 = entidad
        x2 = Poly1.Coordinates(0): y2 = Poly1.Coordinates(1)
        Else
        End If
    Else
    End If
Next
linea 1, x1, y1, 0, x2, y2, 0
ly.EncenderTodos: ly.Activar "0"
AutoCAD.Application.ActiveDocument.SendCommand "PEDIT" & vbCr & "M" & vbCr & "all" & vbCr & vbCr & vbCr & "j" & vbCr & vbCr & vbCr
AislarEntidadesPorLayers
ly.CargarLayersAlliedPumps
For Each entidad In AutoCAD.Application.ActiveDocument.modelspace
If entidad.ObjectName = "AcDbPolyline" Then
Set Poly1 = entidad
Poly1.Offset (thk)
Poly1.Offset (-thk)
Poly1.Delete
Else
End If
Next
AutoCAD.Application.ActiveDocument.SendCommand "PEDIT" & vbCr & "M" & vbCr & "all" & vbCr & vbCr & "j" & vbCr & vbCr & vbCr

'agregado
AutoCAD.Application.ActiveDocument.SendCommand "reg" & vbCr & "all" & vbCr & vbCr
acad.Sombreado Conceptual
'acad.Vista SW_Isometric
'AislarEntidadesPorLayers
ZoomExtents

End Sub
Public Function linea(nombre As Variant, StartX As Variant, StartY As Variant, StartZ As Variant, EndX As Variant, EndY As Variant, EndZ As Variant, Optional Color As Variant, Optional layer As String)
    'Declaración de Variables
    Dim PuntoA(0 To 2) As Double:    Dim PuntoB(0 To 2) As Double
    PuntoA(0) = StartX:     PuntoA(1) = StartY:         PuntoA(2) = StartZ
    PuntoB(0) = EndX:       PuntoB(1) = EndY:           PuntoB(2) = EndZ
    'Creando nueva linea
    Set nombre = AutoCAD.Application.ActiveDocument.modelspace.AddLine(PuntoA, PuntoB)
    On Error Resume Next
    nombre.Color = Color
    nombre.layer = layer
End Function

Public Function ArcFromConsole(StartX As Variant, StartY As Variant, StartZ As Variant, EndX As Variant, EndY As Variant, EndZ As Variant, Radious As Variant)
StartX1 = acad.ChangebyDot(StartX): StartY1 = acad.ChangebyDot(StartY): StartZ1 = acad.ChangebyDot(StartZ)
EndX1 = acad.ChangebyDot(EndX): EndY1 = acad.ChangebyDot(EndY): EndZ1 = acad.ChangebyDot(EndZ)
firstpnt = StartX1 & "," & StartY1: endpnt = EndX1 & "," & EndY1: radi = acad.ChangebyDot(Radious)
AutoCAD.Application.ActiveDocument.SendCommand "arc" & vbCr & firstpnt & vbCr & "e" & vbCr & endpnt & vbCr & "r" & vbCr & radi & vbCr
End Function
Public Function ChangebyDot(value As Variant) As Variant
ChangebyDot = Replace(value, ",", ".")
End Function

'BACKUP
'Linea 1, pnt1(0), pnt1(1), pnt1(2), pnt1(0), pnt1(1) + r0, pnt1(2)
'ArcFromConsole pnt1(0), pnt1(1) + r0, pnt1(2), pnt1(0) - r1, pnt1(1), pnt1(2), radarc1
'Linea 2, pnt1(0), pnt1(1), pnt1(2), pnt1(0) - r1, pnt1(1), pnt1(2)
'ArcFromConsole pnt1(0) - r1, pnt1(1), pnt1(2), pnt1(0), pnt1(1) - r2, pnt1(2), radarc2
'Linea 3, pnt1(0), pnt1(1), pnt1(2), pnt1(0), pnt1(1) - r2, pnt1(2)
'ArcFromConsole pnt1(0), pnt1(1) - r2, pnt1(2), pnt1(0) + r3, pnt1(1), pnt1(2), radarc3
'Linea 4, pnt1(0), pnt1(1), pnt1(2), pnt1(0) + r3, pnt1(1), pnt1(2)
'ArcFromConsole pnt1(0) + r3, pnt1(1), pnt1(2), pnt1(0), pnt1(1) + r4, pnt1(2), radarc4

'TRASH
'Dim PuntoA(0 To 2) As Double:'Dim PuntoB(0 To 2) As Double
'PuntoA(0) = pnt1(0):     PuntoA(1) = pnt1(1):         PuntoA(2) = pnt1(2)
'PuntoB(0) = pnt2(0):     PuntoB(1) = pnt2(1):         PuntoB(2) = pnt2(2)
'Set LineaNew = AutoCAD.Application.ActiveDocument.modelspace.AddLine(PuntoA, PuntoB)

'CONTINUE
'thk = AutoCAD.Application.ActiveDocument.Utility.GetDistance(pnt2, "Thick: ")
'ly.Activar ".GENERAL ARRANGEMENT"
'draw.Circulo acModelSpace, pnt1(0), pnt1(1), pnt1(2), rad1 + thk, acByLayer
'draw.Circulo acModelSpace, pnt2(0), pnt2(1), pnt2(2), rad2 + thk, acByLayer
'draw.Circulo acModelSpace, pnt1(0), pnt1(1), pnt1(2), rad1 - thk, acByLayer
'draw.Circulo acModelSpace, pnt2(0), pnt2(1), pnt2(2), rad2 - thk, acByLayer
'LineaNew.Offset (thk)
'LineaNew.Offset (-thk)

Attribute VB_Name = "Spline"
Dim ly As New EngCad_Autocad_Layers
Dim acad As New EngCad_Autocad_General
Dim acadedit As New EngCad_Autocad_Edition
Dim entidad As AcadEntity
Dim i As Integer
Dim modelspace As AcadModelSpace
Dim PaperSpace As AcadPaperSpace
Dim ssetObj As AcadSelectionSet
Dim layerObj As AcadLayer
Dim LayerCol As AcadLayers
Dim linea As AcadLine
Dim Poly As AcadPolyline
Dim Poly1 As AcadLWPolyline
Dim Poly2 As Acad3DPolyline
Dim spl As AcadSpline

Sub Flatten_Spline_Select() '^C^C-vbarun Flatten_Spline_Select
acadedit.BorrarSelectionSets
Set ssetObj = AutoCAD.Application.ActiveDocument.SelectionSets.Add(Rnd): ssetObj.SelectOnScreen
For Each entidad In ssetObj
If entidad.ObjectName = "AcDbSpline" Then
namelayer = "random" & entidad.ObjectID: ly.nuevo namelayer: ly.Activar namelayer: entidad.layer = namelayer: ly.ApagaExcepto namelayer
AutoCAD.Application.ActiveDocument.SendCommand "flatten" & vbCr & "all" & vbCr & vbCr & "no" & vbCr
Else
MsgBox "La selección no es Spline."
Exit Sub
End If
Next
ly.EncenderTodos: ly.Activar "0": AislarEntidadesPorLayers: ssetObj.Delete 'restore selection
End Sub

Sub Flatten_Spline_All() '^C^C-vbarun Flatten_Spline_All
For Each entidad In AutoCAD.Application.ActiveDocument.modelspace
If entidad.ObjectName = "AcDbSpline" Then
namelayer = "random" & entidad.ObjectID: ly.nuevo namelayer: ly.Activar namelayer: entidad.layer = namelayer: ly.ApagaExcepto namelayer
AutoCAD.Application.ActiveDocument.SendCommand "flatten" & vbCr & "all" & vbCr & vbCr & "no" & vbCr
ly.EncenderTodos: ly.Activar "0"
Else
End If
Next
ly.EncenderTodos: ly.Activar "0": AislarEntidadesPorLayers 'restore all
End Sub

Sub Refine_Spline_All()

End Sub

Attribute VB_Name = "UserForm1"
Attribute VB_Base = "0{DA94F2DA-5AFF-443B-B2BB-3211D777FC4A}{D2AFC0B1-6D62-49A1-8E24-EA88B4404F87}"
Attribute VB_GlobalNameSpace = False
Attribute VB_Creatable = False
Attribute VB_PredeclaredId = True
Attribute VB_Exposed = False
Attribute VB_TemplateDerived = False
Attribute VB_Customizable = False
Dim entidad As AcadEntity
Dim ly As New EngCad_Autocad_Layers
Dim acad As New EngCad_Autocad_General

Private Sub Enter_Click()

UserForm1.Hide

End Sub

Private Sub UserForm_Initialize()

UserForm1.Label1.Caption = " A continuación seleccione el proceso a aplicar a los archivos de la carpeta " & CurrentFolder

UserForm1.ComboBox1.List = Array( _
                                    "Overkill All", _
                                    "Convert Poly to Poly2d")
                                    
                                
End Sub
